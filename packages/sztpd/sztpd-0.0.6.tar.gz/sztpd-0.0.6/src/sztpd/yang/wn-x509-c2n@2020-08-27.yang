module wn-x509-c2n {
  yang-version 1.1;
  namespace "https://watsen.net/wnc2n";
  prefix wnc2n;

  import ietf-x509-cert-to-name {
    prefix x509c2n;
    reference
      "RFC 7407: A YANG Data Model for SNMP Configuration";
  }

  organization
    "Watsen Networks (https://watsen.net)";
  description
    "This module defines identities that extend those defined in
     RFC 7407.

     Copyright (c) 2020 Watsen Networks.  All Rights Reserved.";

  revision 2020-08-27 {
    description
      "Initial version";
  }

  identity serial-number {
    base x509c2n:cert-to-name;
    description
      "Maps the X.520 'serialNumber' attribute in the X.509 certificate's
       'subject' field to a name.  The serialNumber attribute is not to be
       confused with the certificate's serial number, which is in value
       assigned by its issuer.";
    reference
      "RFC 5280: Internet X.509 Public Key Infrastructure Certificate
                 and Certificate Revocation List (CRL) Profile

       X.520:    ITU-T Recommendation X.520 (2005) | ISO/IEC 9594-6:2005,
                 Information technology - Open Systems Interconnection -
                 The Directory: Selected attribute types.";
  }
}
